-- Dynamic-Network-Directory-Service-Protocol-V1
-- Copyright (C) Nicolas J. Bouliane - 2010-2013

-- DN> Dynamic Network
-- DS> Directory Service

-- asn1c dnds.asn1 -fnative-types -fskeletons-copy

DNDS DEFINITIONS AUTOMATIC TAGS ::=
BEGIN

uint32max INTEGER ::= 4294967295 -- (2^^32 - 1)

DNDSMessage ::= SEQUENCE {
	version		INTEGER (0..uint32max),
	channel		INTEGER (0..127),
	pdu		CHOICE {			-- Protocol Data Unit
		dnm		DNMessage,
		dsm		DSMessage,
		ethernet	BIT STRING,
		...					-- Extension marker
	}
}

DNDSResult ::= ENUMERATED {
		success				(1),
		operationError			(2),
		protocolError			(3),
		noSuchObject			(4),
		busy				(5),
		secureStepUp			(6),
		insufficientAccessRights	(7),
		...
}

DNMessage ::= SEQUENCE {
	seqNumber	INTEGER (0..uint32max),
	ackNumber	INTEGER (0..uint32max),
	dnop		CHOICE {
		authRequest		AuthRequest,
		authResponse		AuthResponse,
		netinfoRequest		NetinfoRequest,
		netinfoResponse		NetinfoResponse,
		provRequest		ProvRequest,
		provResponse		ProvResponse,
		p2pRequest		P2pRequest,
		p2pResponse		P2pResponse,
		terminateRequest	TerminateRequest,
		...
	}
}

DSMessage ::= SEQUENCE {
	seqNumber	INTEGER (0..uint32max),
	ackNumber	INTEGER (0..uint32max),
	dsop		CHOICE	{
		addRequest		AddRequest,
		addResponse		AddResponse,
		delRequest		DelRequest,
		delResponse		DelResponse,
		modifyRequest		ModifyRequest,
		modifyResponse		ModifyResponse,
		nodeConnectInfo		NodeConnectInfo,
		searchRequest		SearchRequest,
		searchResponse		SearchResponse,
		terminateRequest	TerminateRequest,
		...
	}
}

DNDSObject ::= CHOICE {
	client		Client,
	context		Context,
	node		Node,
	...
}

DNDSObjects ::= SEQUENCE OF DNDSObject

ObjectName ::= ENUMERATED {
	client		(1),
	context		(2),
	node		(3),
	...
}

-------------------------
-- DN> Dynamic Network
-------------------------

AuthRequest ::= SEQUENCE {
	certName	IA5String (SIZE(1..256)),
	...
}

AuthResponse ::= DNDSResult

NetinfoRequest ::= SEQUENCE {
	ipLocal		OCTET STRING (SIZE(4..16)),	-- ipv4 extensible to ipv6
	macAddr		OCTET STRING (SIZE(6)),
	...
}

NetinfoResponse ::= SEQUENCE {
	ipAddress	OCTET STRING (SIZE(4..16)),
	netmask		OCTET STRING (SIZE(4..16)),
	result		DNDSResult,
	...
}

ProvRequest ::= SEQUENCE {
	provCode	PrintableString OPTIONAL,
	...
}

ProvResponse ::= SEQUENCE {
	certificate	PrintableString OPTIONAL,
	certificateKey	PrintableString OPTIONAL,
	trustedCert     PrintableString OPTIONAL,
	ipAddress	OCTET STRING SIZE((4..16)) OPTIONAL,
	...
}

P2pSide ::= ENUMERATED {
	client		(1),
	server		(2),
	...
}

P2pRequest ::= SEQUENCE {
	macAddrDst	OCTET STRING (SIZE(6)),
	ipAddrDst	OCTET STRING (SIZE(4..16)),
	port		INTEGER (0..uint32max),
	side		P2pSide,
	...
}

P2pResponse ::= SEQUENCE {
	macAddrDst	OCTET STRING (SIZE(6)),
	result		DNDSResult,
	...
}

-------------------------
-- DS> Directory Service
-------------------------

AddRequest ::= DNDSObject
AddResponse ::= DNDSResult

DelRequest ::= DNDSObject
DelResponse ::= DNDSResult

ModifyRequest ::= DNDSObject
ModifyResponse ::= DNDSResult

ConnectState ::= ENUMERATED {
	connected	(1),
	disconnected	(2),
	...
}

NodeConnectInfo ::= SEQUENCE {
	certName	IA5String (SIZE(1..256)),
	ipAddr		OCTET STRING (SIZE(4..16)),
	state		ConnectState,
	...
}

SearchType ::= ENUMERATED {
	all		(1),
	sequence	(2),
	object		(3),
	...
}

SearchRequest ::= SEQUENCE {
	searchtype	SearchType,
	objectname	ObjectName OPTIONAL,
	object		DNDSObject OPTIONAL,
	objects		DNDSObjects OPTIONAL,
	...
}

SearchResponse ::= SEQUENCE {
	searchtype	SearchType,
	dndsResult	DNDSResult,
	objects		DNDSObjects,
	...
}

TerminateRequest ::= NULL

Topology ::= ENUMERATED {
	mesh		(1),
	hubspoke	(2),
	gateway		(3),
	...
}

Client ::= SEQUENCE {
	id		INTEGER (0..uint32max) OPTIONAL,
	firstname	PrintableString OPTIONAL,
	lastname	PrintableString OPTIONAL,
	email		IA5String OPTIONAL,
	password	PrintableString OPTIONAL,
	company		PrintableString OPTIONAL,
	phone		PrintableString OPTIONAL,
	country		PrintableString OPTIONAL,
	stateProvince	PrintableString OPTIONAL,
	city 		PrintableString OPTIONAL,
	postalCode	PrintableString OPTIONAL,
	status		INTEGER (0..127) OPTIONAL,
	...
}

Context ::= SEQUENCE {
	id		INTEGER (0..uint32max) OPTIONAL,
	clientId	INTEGER (0..uint32max),
	topology	Topology,
	description	PrintableString SIZE((1..256)) OPTIONAL,
	network         OCTET STRING SIZE((4..16)),
	netmask         OCTET STRING SIZE((4..16)),
	serverCert      PrintableString OPTIONAL,
	serverPrivkey   PrintableString OPTIONAL,
	trustedCert     PrintableString OPTIONAL,
	...
}

Node ::= SEQUENCE {
	contextId	INTEGER (0..uint32max),
	description	PrintableString (SIZE(1..256)) OPTIONAL,
	uuid		PrintableString OPTIONAL,
	provCode	PrintableString OPTIONAL,
	certificate	PrintableString OPTIONAL,
	certificateKey	BIT STRING OPTIONAL,
	trustedCert     PrintableString OPTIONAL,
	ipAddress	OCTET STRING SIZE((4..16)) OPTIONAL,
	status		INTEGER (0..127) OPTIONAL,
	...
}

END
